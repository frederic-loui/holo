module holo-ietf-routing-deviations {
  yang-version 1.1;
  namespace "http://holo-routing.org/yang/holo-ietf-routing-deviations";
  prefix holo-ietf-routing-deviations;

  import ietf-routing {
    prefix rt;
  }

  import ietf-bfd-types {
    prefix bfd-types;
  }

  organization
    "Holo Routing Stack";

  description
    "This module defines deviation statements for the ietf-routing
     module.";

  /*
   * Added constraints
   */

  deviation "/rt:routing/rt:control-plane-protocols/rt:control-plane-protocol" {
    deviate add {
      must 'not(derived-from-or-self(rt:type, "rt:direct"))' {
        error-message
          "The direct protocol isn't configurable.";
      }
      must 'not(derived-from-or-self(rt:type, "bfd-types:bfdv1")) or rt:name = "main"' {
        error-message
          "The BFD protocol instance must be named \"main\".";
      }
    }
  }

  /*
   * Not supported nodes
   */

  deviation "/rt:routing/rt:router-id" {
    deviate not-supported;
  }

  deviation "/rt:routing/rt:interfaces" {
    deviate not-supported;
  }

  deviation "/rt:routing-state" {
    deviate not-supported;
  }

  deviation "/rt:routing/rt:ribs/rt:rib/rt:active-route" {
    deviate not-supported;
  }
}
